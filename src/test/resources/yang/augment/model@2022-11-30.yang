module model {
  yang-version 1.1;
  namespace "urn:ietf:params:xml:ns:yang:model";
  prefix mo;

  revision 2022-11-30 {
    description
      "Initial revision.";
  }

  container data-container {
    list list-data {
      key name;
      unique "year";
      leaf name {
        type string;
      }
      leaf year {
        type int8;
      }
    }
    leaf country {
      type string;
    }
  }
}
